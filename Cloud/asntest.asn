TEST DEFINITIONS ::= BEGIN
    DataUserInput ::= SEQUENCE{
	ipaddress IPADDRESSES,
	operation OPERATIONS,
	postfix POSTFIX
    }

    IPADDRESSES ::= SEQUENCE{
	ipaddress1 OCTET STRING OPTIONAL,
	ipaddress2 OCTET STRING OPTIONAL,
	ipaddress3 OCTET STRING OPTIONAL
	
    }

    OPERATIONS ::= SEQUENCE{
	operation1 OCTET STRING OPTIONAL,
	operation2 OCTET STRING OPTIONAL
    }

    POSTFIX ::= SEQUENCE {
	postfix OCTET STRING OPTIONAL
    }

    DataMd5 ::= SEQUENCE{
        data IA5String
    }

    DataMac ::= SEQUENCE {
        data    IA5String
    }

    DataKey ::= SEQUENCE {
        data OCTET STRING
    }

    DataScalarElement ::= SEQUENCE {
        data    IA5String
    }

    DataStaAp ::= SEQUENCE {
        data    IA5String
    }

    DataFsize ::= SEQUENCE {
        data    INTEGER
    }

    DataContent ::= SEQUENCE{
        data    OCTET STRING
    }

    DataIndicator ::= SEQUENCE {
        data    IA5String
    }

    DataAnsSize ::= SEQUENCE {
        data    INTEGER
    }

    DataAnswer ::= SEQUENCE {
        data    OCTET STRING
    }

END
